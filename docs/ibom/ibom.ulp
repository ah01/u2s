/***************************************************************************************************
                                         USAGE DECLERATION
***************************************************************************************************/
#usage "en: Interactive BOM Data Generator ULP\n"
           "Implements a generator that extracts needed data from a board file \n"
           "and creates the JavaScript JSON variable that is needed for interactive BOM \n"
           "to function\n\n"
           "Usage: RUN ibom.ulp\n"
           "Author: sean.alling@gmail.com"
/**************************************************************************************************/

/***************************************************************************************************
                                         GLOBAL DATA
***************************************************************************************************/
string dirName;
dirName = dlgDirectory("Select a directory", "");
string outputFileName = dirName + "/" +"pcbdata.json";
/**************************************************************************************************/


/**************************************************************************************************
                                         FUNCTIONS DEFINITIONS
***************************************************************************************************/
/*
DESCRIPTION: This function takes the PCB file name, removes the directories and extension.
ASSUMPTIONS:
            1) Project name is the same as board file name (xxx.brd), without the extension
            2) Project does not contain '.'
INPUT: pcbFileName
        File path to the PCB file. 
OUTPUT: Project name

EXAMPLE: INPUT user/project/exampleProject.brd
        OUTPUT exampleProject
*/
string GetProjectName(string pcbFileName)
{
    // Used to hold the project name
    string projectName[];
    // filename(xxx) removes the directory part of the string if it exists. 
    // strsplit splits its input string by looking for '.' and puts the result in projectName
    int n = strsplit(projectName, filename(pcbFileName), '.');
    // The first element (at index 0), contains the filename.
    return projectName[0];
}


/*
    Assumes the user opened a file for printf to write to

    This function is a modified version from what comes with bom.ulp
*/
void GenerateBOM(void )
{
    numeric string bomEntry[];
    numeric string Reference[];
    numeric string Package[];
    numeric string Value[];
    numeric string AttributeName[];
    numeric string AttributeValue[];
    numeric string Location[];

    int n = 0;
    int index[];
    int numBOMEntries = 0;
    string attr[];
    string s;
    string s_val;

    printf("\"bom\": {\n");
    printf("\t\"%s\": [\n","both");
    board(B) 
    {

        // Create three arrays. Each array entry contains information on a part.
        // Three arrays are used to simplify future processing.
        // Iterate over all the strings once
        char printToFile = 0;
        B.elements(E)
        {
            Reference[n] = E.name;
            Package[n]   = E.package.name;
            Value[n]     = E.value;
            string attributeName ="";
            string attributeValue ="";
            E.attributes(A)
            {
                attributeName += A.name + ";";
                attributeValue += A.value + ";";
            }

            // This removes the trailing ;
            if(strlen(attributeName) > 0)
            {
                attributeName[strlen(attributeName)-1] = 0;
            }
            else
            {
                attributeName[0] = 0;
            }

            // This removes the trailing ;
            if(strlen(attributeValue) > 0)
            {
                attributeValue[strlen(attributeValue)-1] = 0;
            }
            else
            {
                attributeValue[0] = 0;
            }
            AttributeName[n] = attributeName;
            AttributeValue[n] = attributeValue;
            if(!E.mirror)
            {
                Location[n] = "F";
            }
            else
            {
                Location[n] = "B";
            }
            
            ++n;
        }

        // Sort all of the parts. Order of sorting for breaking ties goes to package, then value, 
        // and last reference
        sort(n, index, Package, Value, Reference, AttributeName, AttributeValue, Location);

        for (int n2 = 0; n2 < n; ++n2)
        {
            int i1 = index[n2];
            //[1,"1X4_HEADER","1X4_MALE_HEADER_THROUGH_HOLE",[]],
            bomEntry[n2] = "[1," + "\"" + Value[i1] + "\",\"" + Package[i1] + "\",[\"" + Reference[i1] + "\"],\"" + AttributeName[i1] + "\",\"" + AttributeValue[i1] + "\"," + "\"" + Location[i1] + "\"],";
        }

        for (int i = 0; i < n; ++i)
        {
            printf("\t\t%s\n", bomEntry[i]);
        }

    }
    printf("\t],\n");
    printf("},\n");
}

/*
    Define entry for PCB dimensions. This will write to the output file entries for each 
    wire that makes up the output board.
*/
void GenerateDimensions( void )
{
    board(B) {
        // Print to the file the start of the edges section. This will be an array of wire segments
        printf("\"edges\": [\n");
        // Iterate over every wire on the pcb board. 
        B.wires(W){
            /* 
                Check if the wire is on the dimension layer. If the wire is on the dimension layer then
                add a segment object to the output file. 

                The start and end points of the wire segment need to be converted to be in millimeters.
                The type will always be set to segment since the assumption is that the board dimension
                is set using wire segments.

                The widths is the size of the wire.
            */
            if(W.layer == LAYER_DIMENSION){
                printf("\t{\n");
                printf("\t\t\"end\"  : [%5.5f,%5.5f],\n",u2mm(W.x2),u2mm(W.y2));
                printf("\t\t\"start\": [%5.5f,%5.5f],\n",u2mm(W.x1),u2mm(W.y1));
                printf("\t\t\"type\" : \"segment\",\n");
                printf("\t\t\"width\": \"%5.5f\"\n", u2mm(W.width));
                printf("\t},\n");
            }
        }
        printf("],\n");
    }
}

/*
    Add the section for the bounding box. The bounding box is created by looking at the min and max 
    x and y values for the board. The min and max values are defined as the lower left and upper 
    right points that form a box that encapsulates the entire pcb. 
*/
void GenerateBoundingBox( void )
{
    board(B) {
        // Print the edge_box segment to the output file
        printf("\"edges_bbox\": {\n");
        /*
            The min and max values are set by looking at the area parameter of the board. The units 
            need to be converted to millimeters. 

            ASSUMPTION. The pcb lower left corner is also the pcb origin. 
        */
        //TODO: Comparison to select what the min and max values are. This way the lower left corner 
        //      does not need to be the origin.
        printf("\t\t\"maxx\": \"%5.5f\",\n", u2mm(B.area.x1));
        printf("\t\t\"maxy\": \"%5.5f\",\n", u2mm(B.area.y1));
        printf("\t\t\"minx\": \"%5.5f\",\n", u2mm(B.area.x2));
        printf("\t\t\"miny\": \"%5.5f\"\n", u2mm(B.area.y2));
        printf("},\n");
    }
}

void GenerateMetadata( void )
{
    board(B) {
        /*
            Iterate over the board attributes looking for 'COMPANY'. If this attribute exists 
            it returns the value set for 'COMPANY' if set, otherwise returns an empty string.
        */
        string company = "";
        B.attributes(A){
            if( (A.name == "COMPANY") )
            {
                company = A.value;
            }
        }
        
        /*
            Iterate over the board attributes looking for 'REV' or 'REVISION'. If this attribute exists 
            it returns the value set for 'REV' or 'REVISION' if set, otherwise returns an empty string.
        */
        string revision = "";
        B.attributes(A){
            if( (A.name == "REV") || (A.name == "REVISION"))
            {
                revision = A.value;
            }
        }

        /*
            Print the metadata information to file. 
        */
        printf("\"metadata\": {\n");
        printf("\t\t\"company\": \"%s\",\n", company);
        printf("\t\t\"date\": \"%s\",\n", t2string(time(), "Uyyyy-MM-dd hh:mm:ss"));
        printf("\t\t\"revision\": \"%s\",\n", revision);
        printf("\t\t\"title\": \"%s\"\n", GetProjectName(B.name));
        printf("},\n");
    }
}

void GenerateSilkscreen( void )
{
    board(B) {
        printf("\"silkscreen\": {\n");

        printf("\t\"B\": [\n");
        // Extract the text. Going all the way to wires since this can use the segment interface
        // of the rendering
        B.texts(T){
            if(T.layer == LAYER_BPLACE){
                T.wires(W){
                    printf("\t\t{\n");
                    printf("\t\t\t\"end\": [%5.5f,%5.5f],\n",u2mm(W.x2),u2mm(W.y2));
                    printf("\t\t\t\"start\": [%5.5f,%5.5f],\n",u2mm(W.x1),u2mm(W.y1));
                    printf("\t\t\t\"type\": \"segment\",\n");
                    printf("\t\t\t\"width\": \"%5.5f\"\n", u2mm(W.width));
                    printf("\t\t},\n");
                }
            }
        }
        // Extract segments from the packages on the bottom layer. Use the segment 
        // interface for rendering text
        B.elements(E){
            // Mirror is used to signify if the parts on the top or bottom of the board. 
            // mirror = 0 -> top
            // mirror = 1 -> bottom
            if(E.mirror){
                E.package.wires(W){
                    {
                        printf("\t\t{\n");
                        printf("\t\t\t\"end\": [%5.5f,%5.5f],\n",u2mm(W.x2),u2mm(W.y2));
                        printf("\t\t\t\"start\": [%5.5f,%5.5f],\n",u2mm(W.x1),u2mm(W.y1));
                        printf("\t\t\t\"type\": \"segment\",\n");
                        printf("\t\t\t\"width\": \"%5.5f\"\n", u2mm(W.width));
                        printf("\t\t},\n");
                    }
                }
            }
        }
        // TODO: This is not working.
        // Now extract the rectangles for an object.
        //TODO: Make the rectangle interface api similar to that of segment. 
        //      Something along the lines for vertex points so everything else can be calculated
        /*
        B.elements(E){
            // Mirror is used to signify if the parts on the top or bottom of the board.
            // mirror = 0 -> top
            // mirror = 1 -> bottom
            if(E.mirror){
                E.package.rectangles(R){
                        printf("\t\t{\n");
                        printf("\t\t\t\"angle\": [%5.5f],\n",R.angle);
                        printf("\t\t\t\"polygons\": [[\n");
                        printf("\t\t\t\t[%5.5f,%5.5f],\n",u2mm(R.x1), u2mm(R.y1));
                        printf("\t\t\t\t[%5.5f,%5.5f],\n",u2mm(R.x2), u2mm(R.y1));
                        printf("\t\t\t\t[%5.5f,%5.5f],\n",u2mm(R.x2), u2mm(R.y2));
                        printf("\t\t\t\t[%5.5f,%5.5f],\n",u2mm(R.x1), u2mm(R.y2));
                        printf("\t\t\t]],\n");
                        int center_x = (R.x1+R.x2)/2;
                        int center_y = (R.y1+R.y2)/2;
                        printf("\t\t\t\"pos\": [%5.5f,%5.5f],\n",u2mm(R.x2), u2mm(R.y2));
                        printf("\t\t\t\"type\": \"polygon\",\n");
                        printf("\t\t},\n");
                    
                }
            }
        }
        

        B.rectangles(R){
            // Mirror is used to signify if the parts on the top or bottom of the board.
            // mirror = 0 -> top
            // mirror = 1 -> bottom
            {
                printf("\t\t{\n");
                printf("\t\t\t\"angle\": [%5.5f],\n",R.angle);
                printf("\t\t\t\"polygons\": [[\n");
                printf("\t\t\t\t[%5.5f,%5.5f],\n",u2mm(R.x1), u2mm(R.y1));
                printf("\t\t\t\t[%5.5f,%5.5f],\n",u2mm(R.x2), u2mm(R.y1));
                printf("\t\t\t\t[%5.5f,%5.5f],\n",u2mm(R.x2), u2mm(R.y2));
                printf("\t\t\t\t[%5.5f,%5.5f],\n",u2mm(R.x1), u2mm(R.y2));
                printf("\t\t\t]],\n");
                int center_x = (R.x1+R.x2)/2;
                int center_y = (R.y1+R.y2)/2;
                printf("\t\t\t\"pos\": [%5.5f,%5.5f],\n",u2mm(R.x2), u2mm(R.y2));
                printf("\t\t\t\"type\": \"polygon\",\n");
                printf("\t\t},\n");
            
            }
        }
        */
        printf("\t],\n");

        printf("\t\"F\": [\n");
        B.texts(T){
            if(T.layer == LAYER_TPLACE){
                T.wires(W){
                    printf("\t\t{\n");
                    printf("\t\t\t\"end\": [%5.5f,%5.5f],\n",u2mm(W.x2),u2mm(W.y2));
                    printf("\t\t\t\"start\": [%5.5f,%5.5f],\n",u2mm(W.x1),u2mm(W.y1));
                    printf("\t\t\t\"type\": \"segment\",\n");
                    printf("\t\t\t\"width\": \"%5.5f\"\n", u2mm(W.width));
                    printf("\t\t},\n");
                }
            }
        }

        B.elements(E){
            // Mirror is used to signify if the parts on the top or bottom of the board. 
            // mirror = 0 -> top
            // mirror = 1 -> bottom
            if(!E.mirror){
                E.package.wires(W){
                    // Only take wires on the tplace layer
                    if(W.layer == LAYER_TPLACE){
                        printf("\t\t{\n");
                        printf("\t\t\t\"end\": [%5.5f,%5.5f],\n"  ,u2mm(W.x2),u2mm(W.y2));
                        printf("\t\t\t\"start\": [%5.5f,%5.5f],\n",u2mm(W.x1),u2mm(W.y1));
                        printf("\t\t\t\"type\": \"segment\",\n");
                        printf("\t\t\t\"width\": \"%5.5f\"\n", u2mm(W.width));
                        printf("\t\t},\n");
                    }
                }
            }
        }

        printf("\t],\n");

        printf("},\n");
    }
}

void GenerateDeviceEntries( void )
{
    board(B) {
        printf("\"modules\": {\n");

        B.elements(E){
            printf("\t\"%s\": {\n",E.name);


            printf("\t\t\"bbox\":{\n");
            int diff_x = (E.package.area.x2 - E.package.area.x1)/2;
            int diff_y = (E.package.area.y2 - E.package.area.y1)/2;
            printf("\t\t\t\"pos\":[%5.5f,%5.5f],\n",u2mm(E.x - diff_x/2), u2mm(E.y - diff_y/2));
            printf("\t\t\t\"size\":[%5.5f,%5.5f],\n",u2mm(diff_x), u2mm(diff_y));
            printf("\t\t},\n");
            
            printf("\t\t\"center\":[%5.5f,%5.5f],\n",u2mm(E.x), u2mm(E.y));

            printf("\t\t\"drawings\":[],\n");

            if(!E.mirror)
            {
                printf("\t\t\"layer\":[\"F\"],\n");
            }
            else
            {
                printf("\t\t\"layer\":[\"B\"],\n");
            }
            
            printf("\t\t\"pads\":[\n");
            E.package.contacts(C)
            {
                printf("\t\t\t{\n");
                if(C.smd)
                {
                    printf("\t\t\t\t\"angle\": %5.5f,\n",C.smd.angle);
                }
                else if(C.pad)
                {
                    printf("\t\t\t\t\"angle\": %5.5f,\n",C.pad.angle);
                }

                // Checks if the part is smd or through hole.
                if(C.smd)
                {
                    if(!E.mirror)
                    {
                        printf("\t\t\t\t\"layers\":[\"F\"],\n");
                    }
                    else
                    {
                        printf("\t\t\t\t\"layers\":[\"B\"],\n");
                    }
                }
                else if(C.pad)
                {
                   printf("\t\t\t\t\"layers\":[\"F\", \"B\"],\n");
                }



                printf("\t\t\t\t\"offset\": [0.0,0.0],\n");
                if(C.name=="1")
                {
                    printf("\t\t\t\t\"pin1\":%s,\n","1");
                }
                else
                {
                    printf("\t\t\t\t\"pin1\":%s,\n","0");
                }
                printf("\t\t\t\t\"pos\": [%5.5f,%5.5f],\n",u2mm(C.x), u2mm(C.y));
                printf("\t\t\t\t\"shape\": \"rect\",\n");
                
                if(C.smd)
                {
                    printf("\t\t\t\t\"size\": [%5.5f,%5.5f],\n",u2mm(C.smd.dx), u2mm(C.smd.dy));
                    printf("\t\t\t\t\"type\": \"smd\"\n");
                }
                else if(C.pad)
                {
                    printf("\t\t\t\t\"size\": [%5.5f,%5.5f],\n",1.0, 1.0);
                    printf("\t\t\t\t\"type\": \"smd\"\n");
                }
                
                printf("\t\t\t},\n");
            }
            printf("\t\t],\n");

            printf("\t\t\"ref\":\"%s\"\n",E.name);

            printf("\t},\n");
        }

        printf("},\n");
    }
}
/**************************************************************************************************/

output(outputFileName,"wt")
{
    printf("var pcbdata =  {\n");
    GenerateBOM();
    GenerateDimensions();
    GenerateBoundingBox();
    GenerateMetadata();
    GenerateSilkscreen();
    GenerateDeviceEntries();
    printf("}");
}
